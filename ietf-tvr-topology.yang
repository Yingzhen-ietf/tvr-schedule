module ietf-tvr-topology {
  yang-version 1.1;
  namespace "urn:ietf:params:xml:ns:yang:ietf-tvr-topology";
  prefix tvr-topo;

  import ietf-inet-types {
    prefix inet;
    reference
      "RFC 9911: Common YANG Data Types";
  }
  import ietf-yang-types {
    prefix yang;
    reference
      "RFC 9911: Common YANG Data Types";
  }
  import ietf-tvr-schedule {
    prefix tvr-schd;
    reference
      "RFC XXXX: A YANG Data Model for Scheduled Attributes";
  }

  import ietf-network {
    prefix nw;
    reference
      "RFC 8345: A YANG Data Model for Network Topologies";
  }


  import ietf-network-topology {
    prefix nt;
    reference
      "RFC 8345: A YANG Data Model for Network Topologies";
  }  

  organization
    "IETF Time-Variant Routing Working Group";
  contact
    "WG Web:   <https://datatracker.ietf.org/wg/tvr/>
     WG List:  <mailto:tvr@ietf.org>

     Author:   Eric Kinzie
               <mailto:ekinzie@labn.net>
     Author:   Don Fedyk
               <mailto:dfedyk@labn.net>
     Author:   Yingzhen Qu
               <mailto:yingzhen.ietf@gmail.com>
     Author:   Acee Lindem
               <mailto:acee.ietf@gmail.com>
     Author:   Marc Blanchet
               <mailto:marc.blanchet@viagenie.ca>";
  description
    "This YANG module contains YANG definitions for describing
     network topology with a time-variant availability schedule.

     Copyright (c) 2026 IETF Trust and the persons identified as
     authors of the code.  All rights reserved.

     Redistribution and use in source and binary forms, with or
     without modification, is permitted pursuant to, and subject to
     the license terms contained in, the Revised BSD License set forth
     in Section 4.c of the IETF Trust's Legal Provisions Relating
     to IETF Documents (https://trustee.ietf.org/license-info).

     All revisions of IETF and IANA published modules can be found
     at the YANG Parameters registry group
     (https://www.iana.org/assignments/yang-parameters).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-06-11 {
    description
      "Initial revision";
    reference
      "RFC XXXX: A YANG Data Model for Scheduled Attributes";
  }

  grouping node-availability-schedule {
    description
      "Node availability scheduling - reusable grouping specifying
       node availability scheduling.";
    container available {
      description
        "The time at which this node becomes available.";
      leaf default-node-available {
        type boolean;
        default "false";
        description
          "By default, the node is powered off.";
      }
      uses tvr-schd:tvr-schedule {
        augment "schedule" {
          description
            "Augment scheduled node availability.";
          leaf node-available {
            type boolean;
            description
              "Node availability.";
          }
        }
      }
    }
  }

  grouping link-availability-schedule {
    description
      "Link availability scheduling - reusable grouping specifying
       link availability scheduling.";
    container available {
      description
        "The time at which this link becomes available.";
      uses tvr-schd:tvr-schedule {
        augment "schedule" {
          description
            "Augment scheduled values.";
          container link-attributes {
            description
              "Augmentation container for links.";
            leaf link-available {
              type boolean;
              description
                "The predicted link availability.";
            }
            leaf bandwidth {
              type yang:gauge64;
              units "bits/second";
              description
                "The predicted link capacity. If the value measured
                 by the system is less than this value, the system
                 value is used. If the value measured by the system
                 is greater than this value the predicted value
                 SHOULD be used.";
            }
            leaf delay {
              type uint64;
              units "microseconds";
              description
                "The predicted one-way delay or latency in
                 microseconds. If the value measured by the system is
                 less than this value the predicted value SHOULD be
                 used.";
            }
            leaf-list destination-nodes {
              type inet:uri;
              description
                "A list of one or more destination nodes that are
                 associated with the link schedule.";
            }
            leaf strict-destination-checking {
              when "../destination-nodes" {
                description
                  "This is only relevant when destination node(s)
                   are specified.";
              }
              type boolean;
              default 'false';
              description
               "Indicates whether or not the specified destination
                node(s) are the only destinations allowed when the
                link schedule is active";
           }
          }
        }
      }
      leaf default-link-available {
        type boolean;
        default "false";
        description
          "The default link availability.  During times when the
           schedule does not specify an availability, this value
           is used.";
      }
      leaf default-bandwidth {
        type yang:gauge64;
        units "bits/second";
        default "0";
        description
          "The default link capacity specified in a
           generic format.";
      }
      leaf default-delay {
        type uint64;
        units "microseconds";
        description
          "The default one-way delay in microseconds.";
      }
    }
  }

  augment "/nw:networks/nw:network/nw:network-types" {
    description
      "Introduces a new network type for TVR topology.";
    container tvr-topology {
      presence
        "Indicates this is a TVR topology, with TVR
         attributes.";
      description
        "Container for the TVR network type.
         When present, it signals that the network contains
         TVR augmentations.";
    }
  }

  augment "/nw:networks/nw:network/nw:node" {
    when "../nw:network-types/tvr-topo:tvr-topology";
    description
      "Augment network node with schedules.";
    uses node-availability-schedule;
  }

  augment "/nw:networks/nw:network/nw:node/nt:termination-point" {
    when "../../nw:network-types/tvr-topo:tvr-topology";
    description
      "Augment network link with schedules.";
    uses link-availability-schedule;
  }
}
